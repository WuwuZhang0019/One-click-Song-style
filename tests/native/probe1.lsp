;;; probe1.lsp - S01 environment probe (temporary development file)
(defun c:OCS_PROBE ( / f ver eng )
  (setq f (open "H:\\coding\\一键改宋体\\One-click-Song-style\\tests\\native\\scratch\\probe1.out" "w"))
  (write-line "--- OCS PROBE 1 ---" f)
  (setq ver (getvar "ACADVER"))
  (write-line (strcat "ACADVER=" ver) f)
  (write-line (strcat "PRODUCT=" (getvar "PRODUCT")) f)
  (write-line (strcat "MENUNAME=" (getvar "MENUNAME")) f)
  (write-line (strcat "PLATFORM=" (getvar "PLATFORM")) f)
  (write-line (strcat "LISPSYS=" (itoa (getvar "LISPSYS"))) f)
  (write-line (strcat "FONTALT=" (getvar "FONTALT")) f)
  (write-line (strcat "FONTMAP=" (getvar "FONTMAP")) f)
  (write-line (strcat "SECURELOAD=" (itoa (getvar "SECURELOAD"))) f)
  (write-line (strcat "CMC-OK=" (if (vl-catch-all-error-p (vl-catch-all-apply 'vla-get-Color '((vla-get-ActiveDocument (vlax-get-acad-object))))) "NO" "YES")) f)
  (write-line (strcat "UNDOCTL=" (itoa (getvar "UNDOCTL"))) f)
  (write-line (strcat "CMDECHO=" (itoa (getvar "CMDECHO"))) f)
  ;; font existence
  (write-line (strcat "FINDFILE simsun.ttc=" (if (findfile "simsun.ttc") "YES" "NO")) f)
  (write-line (strcat "FINDFILE simsun.ttf=" (if (findfile "simsun.ttf") "YES" "NO")) f)
  (write-line (strcat "FINDFILE SIMSUN.TTF=" (if (findfile "SIMSUN.TTF") "YES" "NO")) f)
  (write-line (strcat "FINDFILE SimSun.ttc=" (if (findfile "SimSun.ttc") "YES" "NO")) f)
  (write-line (strcat "FINDFILE simhei.ttf=" (if (findfile "simhei.ttf") "YES" "NO")) f)
  ;; create a temp style and test FontFile/BigFont write+readback
  (OCS_PROBE_STYLE f)
  (write-line "--- PROBE 1 END ---" f)
  (close f)
  (princ)
)
(defun OCS_PROBE_STYLE ( f / doc st objs ent big old70 res )
  (setq doc (vla-get-ActiveDocument (vlax-get-acad-object)))
  (setq res "OK")
  (vl-catch-all-apply
    '(lambda ()
       ;; make sure it does not exist
       (vl-catch-all-apply 'command (list "-PURGE" "ST" "*" "N"))
       (setq st (vla-AddTextStyle doc "OCSPROBE" "txt" T))
     )
    nil
  )
  (write-line (strcat "ADD-STYLE=" res) f)
  (setq objs (vla-get-TextStyles doc))
  (setq ent (tblobjname "STYLE" "OCSPROBE"))
  (if ent
    (progn
      (setq old70 (cdr (assoc 70 (entget ent))))
      (write-line (strcat "STYLE-FOUND 70=" (itoa old70)) f)
      ;; read current FontFile / BigFontFile
      (vl-catch-all-apply
        '(lambda ( / o )
           (setq o (vlax-ename->vla-object ent))
           (write-line (strcat "FontFile-before=" (vla-get-FontFile o)) f)
           (write-line (strcat "BigFontFile-before=" (vla-get-BigFontFile o)) f)
           ;; try TrueType simsun
           (setq r (vl-catch-all-apply 'vla-put-FontFile (list o "simsun.ttc")))
           (if (vl-catch-all-error-p r)
             (write-line (strcat "PUT-FONTFILE-simsun.ttc=ERR " (vl-catch-all-error-message r)) f)
             (write-line "PUT-FONTFILE-simsun.ttc=OK" f))
           (setq r (vl-catch-all-apply 'vla-SetFont (list o 68 "宋体" 0 0 1 255)))
           (if (vl-catch-all-error-p r)
             (write-line (strcat "SETFONT-song=ERR " (vl-catch-all-error-message r)) f)
             (write-line "SETFONT-song=OK" f))
           (write-line (strcat "FontFile-after=" (vla-get-FontFile o)) f)
           (write-line (strcat "BigFontFile-after=" (vla-get-BigFontFile o)) f)
           ;; set a bigfont first, then clear via DXF 4
           (setq r (vl-catch-all-apply 'vla-put-BigFontFile (list o "hz.shx")))
           (if (vl-catch-all-error-p r)
             (write-line (strcat "PUT-BIGFONT=ERR " (vl-catch-all-error-message r)) f)
             (write-line "PUT-BIGFONT=OK" f))
           (write-line (strcat "BigFontFile-with=" (vla-get-BigFontFile o)) f)
           (setq r (vl-catch-all-apply 'vla-put-BigFontFile (list o "")))
           (if (vl-catch-all-error-p r)
             (write-line (strcat "PUT-BIGFONT-EMPTY=ERR " (vl-catch-all-error-message r)) f)
             (write-line "PUT-BIGFONT-EMPTY=OK" f))
           (write-line (strcat "BigFontFile-putempty=" (vla-get-BigFontFile o)) f)
           ;; DXF 4 clear
           (setq ent (tblobjname "STYLE" "OCSPROBE"))
           (setq r (vl-catch-all-apply 'entmod (list (subst (cons 4 "") (assoc 4 (entget ent)) (entget ent)))))
           (if (vl-catch-all-error-p r)
             (write-line (strcat "ENTMOD-CLEAR4=ERR " (vl-catch-all-error-message r)) f)
             (write-line "ENTMOD-CLEAR4=OK" f))
           (setq ent (tblobjname "STYLE" "OCSPROBE"))
           (write-line (strcat "DXF4-after-entmod=[" (cdr (assoc 4 (entget ent))) "]") f)
           (setq ent (tblobjname "STYLE" "OCSPROBE"))
           (setq o (vlax-ename->vla-object ent))
           (write-line (strcat "BigFontFile-after-entmod=" (vla-get-BigFontFile o)) f)
           (write-line (strcat "FontFile-final=" (vla-get-FontFile o)) f)
           (write-line (strcat "Height=" (itoa (fix (vla-get-Height o))) ) f)
           (write-line (strcat "Width=" (rtos (vla-get-Width o) 2 4)) f)
           (write-line (strcat "ObliqueAngle=" (rtos (vla-get-ObliqueAngle o) 2 4)) f)
           (write-line (strcat "LastFontFile=" (vla-get-LastFontFile o)) f)
         )
        nil
      )
    )
    (write-line "STYLE-NOT-FOUND" f)
  )
  (princ)
)
(princ)
