;;; sub12/f08 - 主源码第 2493-2497 行（part12 第 8 个顶层 form）
;;; 由 tools/build_diag.py 生成；加载成功打印 OK-F08
(if (and (boundp '*OCS:Version*) *OCS:Version*)
  (princ (strcat "\n一键统一宋体（YJST）v" *OCS:Version*
                 " 已加载。输入 YJST 执行。"))
  (princ "\n一键统一宋体（YJST）已加载。输入 YJST 执行。")
)
(princ "\nOK-F08 lines 2493-2497")
(princ)
