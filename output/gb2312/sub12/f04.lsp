;;; sub12/f04 - 主源码第 2544-2548 行（part12 第 4 个顶层 form）
;;; 由 tools/build_diag.py 生成；加载成功打印 OK-F04
(if (and (boundp '*OCS:Version*) *OCS:Version*)
  (princ (strcat "\n一键统一宋体（YJST）v" *OCS:Version*
                 " 已加载。输入 YJST 执行。"))
  (princ "\n一键统一宋体（YJST）已加载。输入 YJST 执行。")
)
(princ "\nOK-F04 lines 2544-2548")
(princ)
