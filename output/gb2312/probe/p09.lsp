;;; probe p09 (09/13) - 引擎特性测试：vl-load-com（主源码第一个顶层求值形式）
;;; 由 tools/build_diag.py 生成；加载成功应看到 PROBE-09-OK 标记
;;; probe p09 - vl-load-com (first top-level form of main file)
(vl-load-com)
(princ "\nPROBE-09-OK vl-load-com")
